module gnmi-yang-storage {
    yang-version 1;
    namespace "urn:lighty:gnmi:yang:storage";
    prefix "gnmi-ys";

    description
        "Model used for storing yang models from which schema contexts of gNMI devices are constructed.

         Copyright (c) 2021 PANTHEON.tech s.r.o. All Rights Reserved.

         This program and the accompanying materials are made available under the
         terms of the Eclipse Public License v1.0 which accompanies this distribution,
         and is available at https://www.eclipse.org/legal/epl-v10.html";

    revision "2021-03-31" {
        description "Initial revision of gNMI yang storage model";
    }

    import gnmi-yang-model-types { prefix gnmi-ymt; revision-date "2021-07-02";}

    container gnmi-yang-models {
        list gnmi-yang-model {
            key "name version";
            config false;
            uses gnmi-ymt:yang-model;
        }
    }

    rpc upload-yang-model {
        input {
            uses gnmi-ymt:yang-model;
        }
    }

}
