module gnmi-forced-capabilities {
    yang-version 1;
    namespace "urn:lighty:gnmi:forced-capabilities";
    prefix "gnmi-fc";

    description
        "Model used for storing yang models from which schema contexts of gNMI devices are constructed.

         Copyright (c) 2021 PANTHEON.tech s.r.o. All Rights Reserved.

         This program and the accompanying materials are made available under the
         terms of the Eclipse Public License v1.0 which accompanies this distribution,
         and is available at https://www.eclipse.org/legal/epl-v10.html";

    revision "2021-03-31" {
        description "Initial revision of gNMI force capabilities";
    }

    import network-topology { prefix nt; revision-date 2013-10-21; }
    import yang-ext { prefix ext; revision-date "2013-07-09";}
    import gnmi-topology { prefix gnmi; revision-date "2021-03-16";}
    import gnmi-yang-model-types { prefix gnmi-ymt; revision-date "2021-07-02";}

    grouping forced-yang-models {
        list forced-capability {
            description "List of capabilities that restrict the
                         use of the models. The client restricts the set of data
                         models to be used when interacting with the target.
                         The target must not utilize data tree elements that
                         are defined in schema modules outside the specified list
                         of capabilities.";
            key "name version";
            uses gnmi-ymt:yang-model-name-version;
        }
    }

    augment "/nt:network-topology/nt:topology/nt:node/gnmi:extensions-parameters" {
        ext:augment-identifier "forced-capabilities";

        uses forced-yang-models;
    }
}
